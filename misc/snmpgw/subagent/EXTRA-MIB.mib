EXTRA-MIB DEFINITIONS ::= BEGIN

IMPORTS
    MODULE-IDENTITY, OBJECT-TYPE, NOTIFICATION-TYPE,
    Integer32, enterprises FROM SNMPv2-SMI
    DisplayString, RowStatus, TruthValue
        FROM SNMPv2-TC
    MODULE-COMPLIANCE, OBJECT-GROUP, NOTIFICATION-GROUP
        FROM SNMPv2-CONF
    tailf, hostEntry, hostNumberOfServers, numberOfHosts
        FROM SIMPLE-MIB;


extraMIB MODULE-IDENTITY
    LAST-UPDATED "200702080000Z" -- Feb 07, 2007
    ORGANIZATION "Tail-F Systems AB
                  http://www.tail-f.com"
    CONTACT-INFO
            "        Ola Samuelsson
             E-mail: ola@tail-f.com"
    DESCRIPTION
            "Basic test objects for CONFD-SNMP integration."
    REVISION      "200702080000Z"
    DESCRIPTION
            "First version."
    ::= { tailf 4 }

-- Administrative assignments ++++---------------------------------

extraMIBObjects        OBJECT IDENTIFIER ::= { extraMIB 1 }
extraMIBConformance    OBJECT IDENTIFIER ::= { extraMIB 2 }

-- ----------------------------------------------------------------

extraTables        OBJECT IDENTIFIER ::= { extraMIBObjects 1 }
extraNotifications OBJECT IDENTIFIER ::= { extraMIBObjects 2 }

-- ------------------------------------------------------

extraHostTable  OBJECT-TYPE
    SYNTAX       SEQUENCE OF ExtraHostEntry
    MAX-ACCESS   not-accessible
    STATUS       current
    DESCRIPTION    "test"
    ::= { extraTables 1 }

extraHostEntry OBJECT-TYPE
    SYNTAX       ExtraHostEntry
    MAX-ACCESS   not-accessible
    STATUS       current
    DESCRIPTION
        "test"
    AUGMENTS       { hostEntry }
    ::= { extraHostTable 1 }

ExtraHostEntry ::= SEQUENCE {
    extraHostValue            DisplayString
}

extraHostValue OBJECT-TYPE
    SYNTAX      DisplayString
    MAX-ACCESS  read-create
    STATUS      current
    DESCRIPTION
        "test"
    ::= { extraHostEntry 1 }

-- Notifications ----------------------------------------------------

extraTraps        OBJECT IDENTIFIER ::= { extraNotifications 1 }

extraNotif1 NOTIFICATION-TYPE
    OBJECTS { numberOfHosts }
    STATUS  current
    DESCRIPTION
            "test notification"
    ::= { extraTraps 1 }

extraNotif2 NOTIFICATION-TYPE
    OBJECTS { hostNumberOfServers }
    STATUS  current
    DESCRIPTION
            "test notification"
    ::= { extraTraps 2 }

extraNotif3 NOTIFICATION-TYPE
    OBJECTS { extraHostValue }
    STATUS  current
    DESCRIPTION
            "test notification"
    ::= { extraTraps 3 }

-- Conformance ----------------------------------------------------
extraMIBCompliances OBJECT IDENTIFIER ::= { extraMIBConformance 1 }
extraMIBGroups      OBJECT IDENTIFIER ::= { extraMIBConformance 2 }


-- compliance statements

extraMIBCompliance MODULE-COMPLIANCE
    STATUS  current
    DESCRIPTION
            "The compliance statement for SNMPv2 entities which
            implement the SNMPv2 MIB."
    MODULE  -- this module
        MANDATORY-GROUPS { extraGroup, extraNotificationsGroup }

        GROUP   extraGroup
        DESCRIPTION
            "This group is mandatory for SNMPv2 entities which
            support community-based authentication."

    ::= { extraMIBCompliances 2 }


-- units of conformance

extraGroup OBJECT-GROUP
    OBJECTS {
    -- extraHostTable
    extraHostValue
    }
    STATUS  current
    DESCRIPTION
            "A collection of objects providing basic instrumentation and
            control of Servers."
    ::= { extraMIBGroups 1 }


extraNotificationsGroup  NOTIFICATION-GROUP
    NOTIFICATIONS {
    extraNotif1,
    extraNotif2,
    extraNotif3
    }
    STATUS  current
    DESCRIPTION
            "The notifications"
    ::= { extraMIBGroups 2 }

END
