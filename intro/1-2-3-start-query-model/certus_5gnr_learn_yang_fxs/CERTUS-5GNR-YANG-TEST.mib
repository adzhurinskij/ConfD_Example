-- Generated by
-- confdc ++emit-mib output/CERTUS-5GNR-YANG-TEST.mib ++oid enterprises.667788.10 ++top certus5gnryangtest ++module CERTUS-5GNR-YANG-TEST -f /usr/local/confd/etc/confd/iana-crypt-hash.fxs /usr/local/confd/etc/confd/iana-hardware.fxs /usr/local/confd/etc/confd/ietf-hardware.fxs /usr/local/confd/etc/confd/ietf-inet-types.fxs /usr/local/confd/etc/confd/ietf-interfaces.fxs /usr/local/confd/etc/confd/ietf-ip.fxs /usr/local/confd/etc/confd/ietf-netconf-acm.fxs /usr/local/confd/etc/confd/ietf-netconf-monitoring.fxs /usr/local/confd/etc/confd/ietf-netconf-notifications.fxs /usr/local/confd/etc/confd/ietf-restconf-monitoring.fxs /usr/local/confd/etc/confd/ietf-yang-library.fxs /usr/local/confd/etc/confd/ietf-yang-types.fxs /usr/local/confd/etc/confd/tailf-aaa.fxs /usr/local/confd/etc/confd/tailf-acm.fxs /usr/local/confd/etc/confd/tailf-common-monitoring.fxs /usr/local/confd/etc/confd/tailf-common-query.fxs /usr/local/confd/etc/confd/tailf-common.fxs /usr/local/confd/etc/confd/tailf-confd-monitoring.fxs /usr/local/confd/etc/confd/tailf-kicker.fxs /usr/local/confd/etc/confd/tailf-netconf-monitoring.fxs /usr/local/confd/etc/confd/tailf-progress.fxs /usr/local/confd/etc/confd/tailf-rollback.fxs /usr/local/confd/etc/confd/tailf-webui.fxs /usr/local/confd/etc/confd/tailf-xsd-types.fxs ++ output/certus-5gnr-yang-test.fxs
-- 2019-04-27 19:13:38
-- Namespace: http://certusnet.com/5gnr/du/certus-5gnr-yang-test

CERTUS-5GNR-YANG-TEST DEFINITIONS ::= BEGIN
IMPORTS
    enterprises, MODULE-IDENTITY, OBJECT-TYPE,
    Integer32, Unsigned32, Counter32, Counter64,
    Gauge32, IpAddress
        FROM SNMPv2-SMI
    TEXTUAL-CONVENTION, RowStatus, DateAndTime,
    TruthValue
        FROM SNMPv2-TC
;

certus5gnryangtest MODULE-IDENTITY
    LAST-UPDATED "201904080000Z"
    ORGANIZATION "@ORGANIZATION"
    CONTACT-INFO "@CONTACT-INFO"
    DESCRIPTION "This module defines the YANG definitions for manage the CertusNet 5GNR GNB DU Unit"
    REVISION "201904080000Z"
    DESCRIPTION "@REVISION-DESCRIPTION"
    ::= { enterprises 667788 10 }

UnsignedByte ::= TEXTUAL-CONVENTION
    DISPLAY-HINT "d"
    STATUS      current
    DESCRIPTION "xs:unsignedByte"
    SYNTAX      Unsigned32 (0 .. 255)

ConfdString ::= TEXTUAL-CONVENTION
    DISPLAY-HINT "1t"
    STATUS      current
    DESCRIPTION "xs: and confd: types mapped to strings"
    SYNTAX      OCTET STRING

String ::= TEXTUAL-CONVENTION
    DISPLAY-HINT "1t"
    STATUS      current
    DESCRIPTION "xs:string"
    SYNTAX      OCTET STRING

Resource ::= TEXTUAL-CONVENTION
    DISPLAY-HINT "1t"
    STATUS      current
    DESCRIPTION ""
    SYNTAX      OCTET STRING

-- tagpath /allcontainer
allcontainer OBJECT IDENTIFIER ::= { certus5gnryangtest 1 }

-- tagpath /allcontainer/containerabc
allcontainerContainerabc OBJECT IDENTIFIER ::= { allcontainer 1 }

-- tagpath /allcontainer/containerabc/intleaf
intleaf OBJECT-TYPE
    SYNTAX      Unsigned32
    MAX-ACCESS  read-write
    STATUS      current
    DESCRIPTION ""
    ::= { allcontainerContainerabc 1 }

-- tagpath /allcontainer/containerabc/intleaf2
intleaf2 OBJECT-TYPE
    SYNTAX      Unsigned32
    MAX-ACCESS  read-write
    STATUS      current
    DESCRIPTION ""
    ::= { allcontainerContainerabc 2 }

-- tagpath /allcontainer/refcontainerabc
allcontainerRefcontainerabc OBJECT IDENTIFIER ::= { allcontainer 2 }

-- tagpath /allcontainer/refcontainerabc/refintleaf
allcontainerRefcontainerabcRefintleaf OBJECT-TYPE
    SYNTAX      Unsigned32
    MAX-ACCESS  read-write
    STATUS      current
    DESCRIPTION ""
    ::= { allcontainerRefcontainerabc 1 }

-- tagpath /try-feature
try-feature OBJECT IDENTIFIER ::= { certus5gnryangtest 2 }

-- tagpath /try-feature/arpe
trycallpointTable OBJECT-TYPE
    SYNTAX      SEQUENCE OF TrycallpointEntry
    MAX-ACCESS  not-accessible
    STATUS      current
    DESCRIPTION ""
    ::= { try-feature 1 }

-- tagpath /try-feature/arpe
trycallpointEntry OBJECT-TYPE
    SYNTAX      TrycallpointEntry
    MAX-ACCESS  not-accessible
    STATUS      current
    DESCRIPTION ""
    INDEX { trycallpointDuid }
        ::= { trycallpointTable 1 }

TrycallpointEntry ::=
    SEQUENCE {
        trycallpointDuid UnsignedByte,
        trycallpointRowstatus RowStatus,
        trycallpointIfname String
    }

-- tagpath /try-feature/arpe/duid
trycallpointDuid OBJECT-TYPE
    SYNTAX      UnsignedByte
    MAX-ACCESS  not-accessible
    STATUS      current
    DESCRIPTION ""
    ::= { trycallpointEntry 1 }

-- tagpath /try-feature/arpe/rowstatus
trycallpointRowstatus OBJECT-TYPE
    SYNTAX      RowStatus
    MAX-ACCESS  read-create
    STATUS      current
    DESCRIPTION ""
    ::= { trycallpointEntry 2 }

-- tagpath /try-feature/arpe/ifname
trycallpointIfname OBJECT-TYPE
    SYNTAX      String
    MAX-ACCESS  read-create
    STATUS      current
    DESCRIPTION ""
    ::= { trycallpointEntry 3 }

END
