module example-jukebox-ann {
  namespace "urn:dummy";
  prefix dummy;

  import tailf-common {
    prefix tailf;
  }
  import example-jukebox {
    prefix x;
  }

  description
    "Annotation module for the generated dhcp YANG module";

  tailf:annotate "/x:jukebox" {
    tailf:cdb-oper;
  }
}
