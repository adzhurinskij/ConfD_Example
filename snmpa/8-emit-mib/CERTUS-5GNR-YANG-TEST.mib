-- Generated by
-- confdc ++emit-mib CERTUS-5GNR-YANG-TEST.mib ++oid enterprises.667788.10 ++top certus5gnryangtest -f /usr/local/confd/etc/confd/iana-crypt-hash.fxs /usr/local/confd/etc/confd/iana-hardware.fxs /usr/local/confd/etc/confd/ietf-hardware.fxs /usr/local/confd/etc/confd/ietf-inet-types.fxs /usr/local/confd/etc/confd/ietf-interfaces.fxs /usr/local/confd/etc/confd/ietf-ip.fxs /usr/local/confd/etc/confd/ietf-netconf-acm.fxs /usr/local/confd/etc/confd/ietf-netconf-monitoring.fxs /usr/local/confd/etc/confd/ietf-netconf-notifications.fxs /usr/local/confd/etc/confd/ietf-restconf-monitoring.fxs /usr/local/confd/etc/confd/ietf-yang-library.fxs /usr/local/confd/etc/confd/ietf-yang-types.fxs /usr/local/confd/etc/confd/tailf-aaa.fxs /usr/local/confd/etc/confd/tailf-acm.fxs /usr/local/confd/etc/confd/tailf-common-monitoring.fxs /usr/local/confd/etc/confd/tailf-common-query.fxs /usr/local/confd/etc/confd/tailf-common.fxs /usr/local/confd/etc/confd/tailf-confd-monitoring.fxs /usr/local/confd/etc/confd/tailf-kicker.fxs /usr/local/confd/etc/confd/tailf-netconf-monitoring.fxs /usr/local/confd/etc/confd/tailf-progress.fxs /usr/local/confd/etc/confd/tailf-rollback.fxs /usr/local/confd/etc/confd/tailf-webui.fxs /usr/local/confd/etc/confd/tailf-xsd-types.fxs ++ certus-5gnr-yang-test.fxs
-- 2019-04-16 15:02:34
-- Namespace: http://certusnet.com/5gnr/du/certus-5gnr-yang-test

CERTUS-5GNR-YANG-TEST DEFINITIONS ::= BEGIN
IMPORTS
    enterprises, MODULE-IDENTITY, OBJECT-TYPE,
    Integer32, Unsigned32, Counter32, Counter64,
    Gauge32, IpAddress
        FROM SNMPv2-SMI
    TEXTUAL-CONVENTION, RowStatus, DateAndTime,
    TruthValue
        FROM SNMPv2-TC
;

certus5gnryangtest MODULE-IDENTITY
    LAST-UPDATED "201904080000Z"
    ORGANIZATION "@ORGANIZATION"
    CONTACT-INFO "@CONTACT-INFO"
    DESCRIPTION "This module defines the YANG definitions for manage the CertusNet 5GNR GNB DU Unit"
    REVISION "201904080000Z"
    DESCRIPTION "@REVISION-DESCRIPTION"
    ::= { enterprises 667788 10 }

UnsignedByte ::= TEXTUAL-CONVENTION
    DISPLAY-HINT "d"
    STATUS      current
    DESCRIPTION "xs:unsignedByte"
    SYNTAX      Unsigned32 (0 .. 255)

String ::= TEXTUAL-CONVENTION
    DISPLAY-HINT "1t"
    STATUS      current
    DESCRIPTION "xs:string"
    SYNTAX      OCTET STRING

-- tagpath /containerabc
containerabc OBJECT IDENTIFIER ::= { certus5gnryangtest 1 }

-- tagpath /containerabc/intleaf
intleaf OBJECT-TYPE
    SYNTAX      Unsigned32
    MAX-ACCESS  read-write
    STATUS      current
    DESCRIPTION ""
    ::= { containerabc 1 }

-- tagpath /containerabc/intleaf2
intleaf2 OBJECT-TYPE
    SYNTAX      Unsigned32
    MAX-ACCESS  read-write
    STATUS      current
    DESCRIPTION ""
    ::= { containerabc 2 }

-- tagpath /refcontainerabc
refcontainerabc OBJECT IDENTIFIER ::= { certus5gnryangtest 2 }

-- tagpath /refcontainerabc/refintleaf
refcontainerabcRefintleaf OBJECT-TYPE
    SYNTAX      Unsigned32
    MAX-ACCESS  read-write
    STATUS      current
    DESCRIPTION ""
    ::= { refcontainerabc 1 }

-- tagpath /trycallpoint/arpe
trycallpointTable OBJECT-TYPE
    SYNTAX      SEQUENCE OF TrycallpointEntry
    MAX-ACCESS  not-accessible
    STATUS      current
    DESCRIPTION ""
    ::= { certus5gnryangtest 3 }

-- tagpath /trycallpoint/arpe
trycallpointEntry OBJECT-TYPE
    SYNTAX      TrycallpointEntry
    MAX-ACCESS  not-accessible
    STATUS      current
    DESCRIPTION ""
    INDEX { trycallpointIndex }
        ::= { trycallpointTable 1 }

TrycallpointEntry ::=
    SEQUENCE {
        trycallpointRowstatus RowStatus,
        trycallpointIndex UnsignedByte,
        trycallpointIfname String
    }

-- tagpath /trycallpoint/arpe/rowstatus
trycallpointRowstatus OBJECT-TYPE
    SYNTAX      RowStatus
    MAX-ACCESS  read-create
    STATUS      current
    DESCRIPTION ""
    ::= { trycallpointEntry 1 }

-- tagpath /trycallpoint/arpe/index
trycallpointIndex OBJECT-TYPE
    SYNTAX      UnsignedByte
    MAX-ACCESS  not-accessible
    STATUS      current
    DESCRIPTION ""
    ::= { trycallpointEntry 2 }

-- tagpath /trycallpoint/arpe/ifname
trycallpointIfname OBJECT-TYPE
    SYNTAX      String
    MAX-ACCESS  read-create
    STATUS      current
    DESCRIPTION ""
    ::= { trycallpointEntry 3 }

END
