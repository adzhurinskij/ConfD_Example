-- Generated by
-- confdc ++emit-mib TAIL-F-SIMPLE-MIB.mib.tmp ++oid enterprises.24961.2 ++top tailfSimpleMIB ++module TAIL-F-SIMPLE-MIB -f /usr/local/confd/etc/confd/iana-crypt-hash.fxs /usr/local/confd/etc/confd/iana-hardware.fxs /usr/local/confd/etc/confd/ietf-hardware.fxs /usr/local/confd/etc/confd/ietf-inet-types.fxs /usr/local/confd/etc/confd/ietf-interfaces.fxs /usr/local/confd/etc/confd/ietf-ip.fxs /usr/local/confd/etc/confd/ietf-netconf-acm.fxs /usr/local/confd/etc/confd/ietf-netconf-monitoring.fxs /usr/local/confd/etc/confd/ietf-netconf-notifications.fxs /usr/local/confd/etc/confd/ietf-restconf-monitoring.fxs /usr/local/confd/etc/confd/ietf-yang-library.fxs /usr/local/confd/etc/confd/ietf-yang-types.fxs /usr/local/confd/etc/confd/tailf-aaa.fxs /usr/local/confd/etc/confd/tailf-acm.fxs /usr/local/confd/etc/confd/tailf-common-monitoring.fxs /usr/local/confd/etc/confd/tailf-common-query.fxs /usr/local/confd/etc/confd/tailf-common.fxs /usr/local/confd/etc/confd/tailf-confd-monitoring.fxs /usr/local/confd/etc/confd/tailf-kicker.fxs /usr/local/confd/etc/confd/tailf-netconf-monitoring.fxs /usr/local/confd/etc/confd/tailf-progress.fxs /usr/local/confd/etc/confd/tailf-rollback.fxs /usr/local/confd/etc/confd/tailf-webui.fxs /usr/local/confd/etc/confd/tailf-xsd-types.fxs ++ simple.fxs
-- 2019-04-15 20:26:45
-- Namespace: http://tail-f.com/ns/simple

TAIL-F-SIMPLE-MIB DEFINITIONS ::= BEGIN
IMPORTS
    enterprises, MODULE-IDENTITY, OBJECT-TYPE,
    Integer32, Unsigned32, Counter32, Counter64,
    Gauge32, IpAddress
        FROM SNMPv2-SMI
    TEXTUAL-CONVENTION, RowStatus, DateAndTime,
    TruthValue
        FROM SNMPv2-TC
;

tailfSimpleMIB MODULE-IDENTITY
    LAST-UPDATED "200912020000Z"
    ORGANIZATION "@ORGANIZATION"
    CONTACT-INFO "@CONTACT-INFO"
    DESCRIPTION ""
    REVISION "200912020000Z"
    DESCRIPTION "@REVISION-DESCRIPTION"
    ::= { enterprises 24961 2 }

UnsignedShort ::= TEXTUAL-CONVENTION
    DISPLAY-HINT "d"
    STATUS      current
    DESCRIPTION "xs:unsignedShort"
    SYNTAX      Unsigned32 (0 .. 65535)

InetAddressIP ::= TEXTUAL-CONVENTION
    STATUS      current
    DESCRIPTION "confd:inetAddressIP"
    SYNTAX      OCTET STRING (SIZE (4|16))

String ::= TEXTUAL-CONVENTION
    DISPLAY-HINT "1t"
    STATUS      current
    DESCRIPTION "xs:string"
    SYNTAX      OCTET STRING

Name-type ::= TEXTUAL-CONVENTION
    DISPLAY-HINT "1t"
    STATUS      current
    DESCRIPTION ""
    SYNTAX      OCTET STRING (SIZE (0 .. 64))

-- tagpath /simple-objects
simple-objects OBJECT IDENTIFIER ::= { tailfSimpleMIB 1 }

-- tagpath /simple-objects/number-of-servers
numberOfServers OBJECT-TYPE
    SYNTAX      UnsignedShort
    MAX-ACCESS  read-only
    STATUS      current
    DESCRIPTION ""
    ::= { simple-objects 1 }

-- tagpath /simple-objects/number-of-hosts
numberOfHosts OBJECT-TYPE
    SYNTAX      UnsignedShort
    MAX-ACCESS  read-only
    STATUS      current
    DESCRIPTION ""
    ::= { simple-objects 2 }

-- tagpath /simple-objects/max-number-of-servers
maxNumberOfServers OBJECT-TYPE
    SYNTAX      UnsignedShort (0 .. 1024)
    MAX-ACCESS  read-write
    STATUS      current
    DESCRIPTION ""
    ::= { simple-objects 3 }

-- tagpath /simple-objects/max-number-of-hosts
maxNumberOfHosts OBJECT-TYPE
    SYNTAX      UnsignedShort
    MAX-ACCESS  read-write
    STATUS      current
    DESCRIPTION ""
    ::= { simple-objects 4 }

-- tagpath /simple-objects/hosts/host
hostTable OBJECT-TYPE
    SYNTAX      SEQUENCE OF HostEntry
    MAX-ACCESS  not-accessible
    STATUS      current
    DESCRIPTION ""
    ::= { simple-objects 5 }

-- tagpath /simple-objects/hosts/host
hostEntry OBJECT-TYPE
    SYNTAX      HostEntry
    MAX-ACCESS  not-accessible
    STATUS      current
    DESCRIPTION ""
    INDEX { hostName }
        ::= { hostTable 1 }

HostEntry ::=
    SEQUENCE {
        hostName Name-type,
        hostEnabled TruthValue,
        hostNumber-of-servers UnsignedShort,
        hostRowstatus RowStatus
    }

-- tagpath /simple-objects/hosts/host/name
hostName OBJECT-TYPE
    SYNTAX      Name-type
    MAX-ACCESS  not-accessible
    STATUS      current
    DESCRIPTION ""
    ::= { hostEntry 1 }

-- tagpath /simple-objects/hosts/host/enabled
hostEnabled OBJECT-TYPE
    SYNTAX      TruthValue
    MAX-ACCESS  read-create
    STATUS      current
    DESCRIPTION ""
    ::= { hostEntry 2 }

-- tagpath /simple-objects/hosts/host/number-of-servers
hostNumber-of-servers OBJECT-TYPE
    SYNTAX      UnsignedShort
    MAX-ACCESS  read-only
    STATUS      current
    DESCRIPTION ""
    ::= { hostEntry 3 }

-- tagpath /simple-objects/hosts/host/rowstatus
hostRowstatus OBJECT-TYPE
    SYNTAX      RowStatus
    MAX-ACCESS  read-create
    STATUS      current
    DESCRIPTION ""
    ::= { hostEntry 4 }

-- tagpath /simple-objects/hosts/host/servers/server
serverTable OBJECT-TYPE
    SYNTAX      SEQUENCE OF ServerEntry
    MAX-ACCESS  not-accessible
    STATUS      current
    DESCRIPTION ""
    ::= { tailfSimpleMIB 6 }

-- tagpath /simple-objects/hosts/host/servers/server
serverEntry OBJECT-TYPE
    SYNTAX      ServerEntry
    MAX-ACCESS  not-accessible
    STATUS      current
    DESCRIPTION ""
    INDEX { hostName, serverName }
        ::= { serverTable 1 }

ServerEntry ::=
    SEQUENCE {
        serverName Name-type,
        serverAddressIp IpAddress,
        serverAddressPort UnsignedShort,
        serverRowstatus RowStatus
    }

-- tagpath /simple-objects/hosts/host/servers/server/name
serverName OBJECT-TYPE
    SYNTAX      Name-type
    MAX-ACCESS  not-accessible
    STATUS      current
    DESCRIPTION ""
    ::= { serverEntry 1 }

-- tagpath /simple-objects/hosts/host/servers/server/address/ip
serverAddressIp OBJECT-TYPE
    SYNTAX      IpAddress
    MAX-ACCESS  read-create
    STATUS      current
    DESCRIPTION ""
    ::= { serverEntry 2 }

-- tagpath /simple-objects/hosts/host/servers/server/address/port
serverAddressPort OBJECT-TYPE
    SYNTAX      UnsignedShort (1 .. 65535)
    MAX-ACCESS  read-create
    STATUS      current
    DESCRIPTION ""
    ::= { serverEntry 3 }

-- tagpath /simple-objects/hosts/host/servers/server/rowstatus
serverRowstatus OBJECT-TYPE
    SYNTAX      RowStatus
    MAX-ACCESS  read-create
    STATUS      current
    DESCRIPTION ""
    ::= { serverEntry 4 }

-- tagpath /simple-objects/services/service
serviceTable OBJECT-TYPE
    SYNTAX      SEQUENCE OF ServiceEntry
    MAX-ACCESS  not-accessible
    STATUS      current
    DESCRIPTION ""
    ::= { simple-objects 6 }

-- tagpath /simple-objects/services/service
serviceEntry OBJECT-TYPE
    SYNTAX      ServiceEntry
    MAX-ACCESS  not-accessible
    STATUS      current
    DESCRIPTION ""
    INDEX { serviceAddress, servicePort-number }
        ::= { serviceTable 1 }

ServiceEntry ::=
    SEQUENCE {
        serviceAddress IpAddress,
        servicePort-number UnsignedShort,
        serviceHost-name Name-type,
        serviceServer-name Name-type,
        serviceUsername String,
        servicePassword String,
        serviceRadius-ip InetAddressIP
    }

-- tagpath /simple-objects/services/service/address
serviceAddress OBJECT-TYPE
    SYNTAX      IpAddress
    MAX-ACCESS  not-accessible
    STATUS      current
    DESCRIPTION ""
    ::= { serviceEntry 1 }

-- tagpath /simple-objects/services/service/port-number
servicePort-number OBJECT-TYPE
    SYNTAX      UnsignedShort (1 .. 65535)
    MAX-ACCESS  not-accessible
    STATUS      current
    DESCRIPTION ""
    ::= { serviceEntry 2 }

-- tagpath /simple-objects/services/service/host-name
serviceHost-name OBJECT-TYPE
    SYNTAX      Name-type
    MAX-ACCESS  read-write
    STATUS      current
    DESCRIPTION ""
    ::= { serviceEntry 3 }

-- tagpath /simple-objects/services/service/server-name
serviceServer-name OBJECT-TYPE
    SYNTAX      Name-type
    MAX-ACCESS  read-write
    STATUS      current
    DESCRIPTION ""
    ::= { serviceEntry 4 }

-- tagpath /simple-objects/services/service/username
serviceUsername OBJECT-TYPE
    SYNTAX      String
    MAX-ACCESS  read-write
    STATUS      current
    DESCRIPTION ""
    ::= { serviceEntry 5 }

-- tagpath /simple-objects/services/service/password
servicePassword OBJECT-TYPE
    SYNTAX      String
    MAX-ACCESS  read-write
    STATUS      current
    DESCRIPTION ""
    ::= { serviceEntry 6 }

-- tagpath /simple-objects/services/service/radius-ip
serviceRadius-ip OBJECT-TYPE
    SYNTAX      InetAddressIP
    MAX-ACCESS  read-write
    STATUS      current
    DESCRIPTION ""
    ::= { serviceEntry 7 }

END
